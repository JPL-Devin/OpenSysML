package StateMachineDemo {
    private import ScalarValues::*;
    
    // Simplified state machine demo
    part def Vehicle {
        state vehicleStates {
            state off;
            state on;
        }
    }
    
    // Complex state machine demos removed - require additional syntax support
}
