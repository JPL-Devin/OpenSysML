// Invalid: A metadata usage must have a concrete type (SysML 7.24 checkMetadataUsageConcreteType; pilot MetadataUsage_Invalid.sysml.xt:104).
package P24MetadataAbstractType {
    item p {
        @Metaobjects::Metaobject;
    }
}
