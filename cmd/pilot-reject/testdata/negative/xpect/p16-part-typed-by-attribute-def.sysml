// Invalid: An occurrence, item or part must be typed by occurrence definitions (SysML 7.9 validatePartUsage; pilot PartUsage_invalid.sysml.xt).
package P16PartTypedByAttributeDef {
    attribute def AttDef;
    part p1 : AttDef;
}
