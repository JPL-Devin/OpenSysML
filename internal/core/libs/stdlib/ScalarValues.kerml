standard library package ScalarValues {
	doc /* Curated placeholder for the SysML v2 ScalarValues library.
	     Uses namespace-core constructs only until the definition/usage
	     grammar (datatype/specializes) is implemented; the real OMG
	     library file drops in here unchanged at that point. */

	namespace Boolean;
	namespace String;
	namespace Integer;
	namespace Rational;
	namespace Real;
	namespace Natural;
	namespace Positive;
}
