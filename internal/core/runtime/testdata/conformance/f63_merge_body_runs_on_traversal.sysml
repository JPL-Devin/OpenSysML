package test {
	private import ScalarValues::*;

	// A merge's body belongs to the traversal, not to every arrival: the token
	// whose succession a guard prunes leaves the merge open, so the merge fires
	// once and states its steps once.
	action orJoin {
		attribute ready : Boolean = false;
		attribute mergeRuns : Integer = 0;
		attribute passed : Integer = 0;

		first start;
		fork split;
		action slow;
		action slower { assign ready := true; }
		merge gate { assign mergeRuns := mergeRuns + 1; }
		action tail { assign passed := mergeRuns; }
		done;

		succession first start then split;
		succession first split then gate;
		succession first split then slow;
		succession first slow then slower;
		succession first slower then gate;
		succession first gate if ready then tail;
		succession first tail then done;
	}
}
